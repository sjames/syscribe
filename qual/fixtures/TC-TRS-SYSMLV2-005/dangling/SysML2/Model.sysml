package Demo {
    variation part def RotorChoice {
        variant part quadVariant : QuadKind {
            @SyscribeFeature {
                featureId = 'FEAT-DOES-NOT-EXIST';
            }
        }
    }
}
